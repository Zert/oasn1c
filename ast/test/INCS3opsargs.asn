INCS3opsargs
--IN-CS3-SSF-SCF-ops-args {ccitt recommendation q 1238 modules(1) in-cs3-ssf-scf-ops-args (8) version1(0)}


DEFINITIONS IMPLICIT TAGS ::= 

BEGIN

IMPORTS

--	common-classes,
--	common-datatypes,
--	errortypes,
--	scf-srf-classes,
--	scf-srf-datatypes,
--	ssf-scf-classes,
--	ssf-scf-datatypes,
--	operationcodes,
--	ros-InformationObjects
--FROM IN-CS3-object-identifiers 
--	{ccitt recommendation q 1238 modules(1) in-cs3-object-identifiers (0) version1(0)}

--	OPERATION

--FROM Remote-Operations-Information-Objects ros-InformationObjects



--	COMMON-BOUNDS
--FROM IN-CS3-Common-Classes common-classes

--	SCF-SSF-BOUNDS
--FROM IN-CS3-SSF-SCF-Classes ssf-scf-classes

--	SCF-SRF-BOUNDS
--FROM IN-CS3-SCF-SRF-Classes scf-srf-classes 


--		opcode-activateServiceFiltering,
--	opcode-activityTest,
--	opcode-analysedInformation,
--	opcode-analyseInformation,
--	opcode-applyCharging,
--	opcode-applyChargingReport,
--	opcode-assistRequestInstructions,
--	opcode-authorizeTermination,
--	opcode-callGap,
--	opcode-callInformationReport,
--	opcode-callInformationRequest,
--	opcode-cancel,
--	opcode-cancelStatusReportRequest,
--	opcode-collectedInformation,
--	opcode-collectInformation,
--	opcode-connect,
--	opcode-connectToResource,
--	opcode-continue,
--	opcode-continueWithArgument,
--	opcode-createCallSegmentAssociation,
--	opcode-createOrRemoveTriggerData,

--	opcode-disconnectForwardConnection,
--	opcode-dFCWithArgument,
--	opcode-disconnectLeg,
--	opcode-entityReleased,
--	opcode-establishTemporaryConnection,
--	opcode-eventNotificationCharging,
--	opcode-eventReportBCSM,
--	opcode-eventReportFacility,
--	opcode-facilitySelectedAndAvailable,
--	opcode-furnishChargingInformation,
--	opcode-holdCallInNetwork,
--	opcode-initialDP,
--	opcode-initiateCallAttempt,
--	opcode-manageTriggerData,
--	opcode-mergeCallSegments,
--	opcode-moveCallSegments,
--	opcode-oAbandon,
--	opcode-oAnswer,
--	opcode-oCalledPartyBusy,
--	opcode-oDisconnect,
--	opcode-oMidCall,
--	opcode-moveLeg,
--	opcode-oNoAnswer,
--	opcode-originationAttempt,
--	opcode-originationAttemptAuthorized,
--	opcode-oSuspended,
--	opcode-reconnect,
--	opcode-releaseCall,
--	opcode-reportUTSI,
--	opcode-requestCurrentStatusReport,
--	opcode-requestEveryStatusChangeReport,
--	opcode-requestFirstStatusMatchReport,
--	opcode-requestNotificationChargingEvent,
--	opcode-requestReportBCSMEvent,
--	opcode-requestReportUTSI,
--	opcode-requestReportFacilityEvent,
--	opcode-resetTimer,
--	opcode-routeSelectFailure,
--	opcode-selectFacility,
--	opcode-selectRoute,
--	opcode-sendChargingInformation,
--	opcode-sendFacilityInformation,
--	opcode-sendSTUI,
--	opcode-serviceFilteringResponse,
--	opcode-setServiceProfile,

--	opcode-splitLeg,
--	opcode-statusReport,
--	opcode-tAnswer,
--	opcode-tBusy,
--	opcode-tDisconnect,
--	opcode-termAttemptAuthorized,
--	opcode-terminationAttempt,
--	opcode-tMidCall,
--	opcode-tNoAnswer,
--	opcode-tSuspended

--FROM IN-CS3-operationcodes operationcodes

--	Extensions,
--	Integer4,
--	InvokeId

--FROM IN-CS3-common-datatypes common-datatypes

	Extensions,
	Integer4,
	InvokeId,
	AccessCode ,


	InformationToSend,
	CollectedInfo ,
	MailBoxID ,
	InformationToRecord ,
	Media,
	ReceivedStatus,
	RecordedMessageID,
	SRFGapCriteria ,
	GenericNumber,
	Code,
	maxRecordedMessageUnits,


			ActionIndicator,
			ActionPerformed,
			AChBillingChargingCharacteristics ,
			AdditionalCallingPartyNumber ,
			AlertingPattern,
			ApplicationTimer,
			AssistingSSPIPRoutingAddress ,
			ATMTrafficDescriptor ,

			BackwardGVNS ,
			BCSMEvent  ,
			BearerCapability ,
			
			CalledDirectoryNumber ,
			CalledPartyBusinessGroupID,
			CalledPartyNumber ,
			CalledPartySubaddress ,
			CallingGeodeticLocation ,
			CallingPartyBusinessGroupID,
			CallingPartyNumber ,
			CallingPartysCategory,
			CallingPartySubaddress ,
			CallProcessingOperationCorrelationID,
			CallReference ,
			CallResult ,
		--	CallSegmentID ,
			Carrier ,
			Cause ,
			CCSS,
			CGEncountered,
			ChargeNumber ,
			ChargingEvent ,
			Component,
			ComponentCorrelationID,
			ComponentType,
			ControlType,
			CorrelationID ,
			CountersValue,
			CreateOrRemoveIndicator,
			CSAID ,
			CutAndPaste,
			DateAndTime,
			DefaultFaultHandling ,
			DestinationRoutingAddress ,
			Digits ,
			DisplayInformation ,
			DpSpecificCommonParameters ,
			XDuration,
			EventSpecificInformationBCSM ,
			EventSpecificInformationCharging ,
			EventTypeBCSM,
			EventTypeCharging ,
			ExportLegsType,
			FacilityGroup,
			FacilityGroupMember,
			FCIBillingChargingCharacteristics ,
			FeatureCode ,
			FeatureRequestIndicator,
			FilteredCallTreatment ,
			FilteringCharacteristics,
			FilteringCriteria ,
			FilteringTimeOut,
			ForwardCallIndicators,
			ForwardGVNS ,
			ForwardingCondition,
			GapCriteria ,
			GapIndicators,
			GapTreatment ,
			GenericName ,
			GenericNumbers ,
			HighLayerCompatibility,
			HoldCause,
		--	initialCallSegment,
			INprofile ,
			INServiceCompatibilityIndication ,
	INServiceCompatibilityResponse,

			IPAvailable ,
			IPRoutingAddress ,
			IPSSPCapabilities ,
			ISDNAccessRelatedInformation ,
		--	LegID,
		--	leg1,
			LocationNumber ,
		--	MiscCallInfo,
			MonitorMode,
			NumberingPlan,
			OriginalCalledPartyID ,
			QoSParameter ,
			ProfileIdentifier ,

			Reason ,
			RedirectingPartyID ,
			RedirectionInformation,
			RegistratorIdentifier,
			ReportCondition,
			RoutingNumber ,
 
			RequestedInformationList ,
			RequestedInformationTypeList,
			RequestedUTSIList ,
			ResourceID ,
			ResourceStatus,
			ResponseCondition,
			RouteList ,
			ScfID ,
			SCIBillingChargingCharacteristics ,
			SDSSinformation ,
			ServiceInteractionIndicators ,
			ServiceInteractionIndicatorsTwo,
			ServiceKey,
			ServiceProfileIdentifier,
			TDPIdentifier,
			TerminalType,
		--	TimerID,
			TimerValue,
			TravellingClassMark ,
			TriggerData,
			TriggerDataIdentifier ,
			TriggerDPType,
			Triggers  ,
			TriggerResults ,
			TriggerStatus,
			TriggerType,
			USIInformation ,
			USIServiceIndicator ,
	VPNIndicator ,


			numOfINProfile,
			numOfBCSMEvents,
			numOfChargingEvents,
			numOfLegs,
			numOfCSs,
--Fix by Hurd
			initialCallSegment

FROM INCS3datatypes  --IN-CS3-SSF-SCF-datatypes ssf-scf-datatypes

--	InformationToSend 

--FROM IN-CS3-scf-srf-datatypes scf-srf-datatypes

--		cancelFailed,
--	eTCFailed,
--	improperCallerResponse,
--	missingCustomerRecord,
--	missingParameter,
--	parameterOutOfRange,
--	requestedInfoError,
--	systemFailure,
--	taskRefused,
--	unavailableResource,
--	unexpectedComponentSequence,
--	unexpectedDataValue,
--	unexpectedParameter,
--	unknownLegID,
--	unknownResource

--FROM IN-CS3-errortypes errortypes
;
-- The following three definitions are local short-hand notation for convenience.
--B1 ::= COMMON-BOUNDS		 defined in Part 1 of Recommendation Q.1238
--B2 ::= SCF-SSF-BOUNDS		 defined in this part (Part 2) of Recommendation Q.1238
--B3 ::= SCF-SRF-BOUNDS		 defined in Part 3 of Recommendation Q.1238

-- *****
-- Definitions of MAP and ISUP types imported above.

CallReferenceNumber ::= INTEGER

ChargingMessageType ::= INTEGER

Ext-BasicServiceCode ::= CHOICE { -- Note: Ext-BasicServiceCode is not defined in MAP!
	bearerService	[2] OCTET STRING (SIZE(1)),
	teleService	[3] OCTET STRING
	}

ISDNAddressString ::= OCTET STRING

OCSIApplicable ::= BOOLEAN

SubscriberState ::= INTEGER

SuppressionOfAnnouncement ::= BOOLEAN

-- *****
-- TYPE DEFINITIONS FOR IN CS-3 ERRORS (Informative).

CancelFailed ::=	SEQUENCE {
			problem		[0] ENUMERATED {
					unknownOperation(0),
					tooLate(1),
					operationNotCancellable(2)
					},
			operation	[1] InvokeId
			}

-- The parameter was not as expected (e.g. missing or out of range).

RequestedInfoError  ::= ENUMERATED {
			unknownRequestedInfo(1),
			requestedInfoNotAvailable(2)
			-- other values FFS
			}

-- The requested information cannot be found.

SystemFailure ::= UnavailableNetworkResource	

-- The operation could not be completed due to a system failure

TaskRefused::= 	ENUMERATED {
			generic(0),
			unobtainable (1),
			congestion(2)
			--other values FFS
			}
-- An entity normally capable of the task requested cannot or chooses not
-- to perform the task at this 
-- time.  This includes error situations like congestion and unobtainable
-- address as used in e.g. the Connect operation.

UnavailableNetworkResource ::= ENUMERATED {
	unavailableResources(0),
	componentFailure(1),
	basicCallProcessingException(2),
	resourceStatusFailure(3),
	endUserFailure(4),
	screening(5)
	}
-- Indicates the network resource that failed
-- Note that in IN CS3 the screening value can only be used by the SCF.

-- *****

-- *****
-- Due to a restriction in SDT it is not possible to denote values of types defined in an inmported
-- module (for example in DEFAULT statements). Therefore the types for which DEFAULT statements are
-- used in this module, are redefined below. The corresponding type definitions in IN-CS2-Datatypes
-- are changed to DTxxx.

CallSegmentID   ::= INTEGER (1..numOfCSs)
-- initialCallSegment INTEGER ::= 1

LegID ::= CHOICE {
	sendingSideID	[0] LegType,
	receivingSideID	[1] LegType
	}

LegType ::= OCTET STRING (SIZE(1))
leg1 LegType ::= '01'H
leg2 LegType ::= '02'H

MiscCallInfo ::= SEQUENCE {
	messageType	[0] ENUMERATED {
			 request(0),
			 notification(1)
			 },
	dpAssignment	[1] ENUMERATED {
			 individualLine(0),
			 groupBased(1),
			 switchBased(2)
			 }	OPTIONAL
	}

TimerID ::= ENUMERATED {
	tssf(0)
	-- others ffs
	}

-- *****


-- Operations and Arguments:

-- Direction: SCF -> SSF, Timer: Tasf 
-- When receiving this operation, the SSF handles calls to destination in a specified manner 
-- without  sending queries for every detected call. It is used for example for providing 
-- televoting or mass calling services. Simple registration functionality (counters) and 
-- announcement control may be  located at the SSF. The operation initializes the specified 
-- counters in the SSF.

ActivateServiceFilteringArg  ::= SEQUENCE {
	filteredCallTreatment		[0] FilteredCallTreatment ,
	filteringCharacteristics		[1] FilteringCharacteristics,
	filteringTimeOut		[2] FilteringTimeOut ,
	filteringCriteria		[3] FilteringCriteria ,
	startTime			[4] DateAndTime		OPTIONAL,
	extensions			[5] Extensions  	 OPTIONAL
	}

-- Direction: SCF -> SSF or SSF-> SCF, Timer: Tat  
-- This operation is used to check for the continued existence of a relationship between the SCF 
-- and SSF. If the relationship is still in existence, then the SSF will respond. If no reply is 
-- received, then the SCF will assume that the SSF has failed in some way and will take the 
-- appropriate action..  As an option, this operation may be used in the reverse direction by the
-- SSF to check for the continued existence of a relationship with the SCF

-- Direction:  SSF -> SCF, Timer: Tadi    
-- This operation is used to indicate availability of routing address and call type. (DP  - 
-- Analysed_Info). 

AnalysedInformationArg ::= SEQUENCE {
	dpSpecificCommonParameters		[0] DpSpecificCommonParameters ,
	dialledDigits					[1] CalledPartyNumber 	OPTIONAL,
	callingPartyBusinessGroupID		[2] CallingPartyBusinessGroupID	OPTIONAL,
	callingPartySubaddress			[3] CallingPartySubaddress 	OPTIONAL,
	callingFacilityGroup				[4] FacilityGroup	OPTIONAL,
	callingFacilityGroupMember		[5] FacilityGroupMember	OPTIONAL,
	originalCalledPartyID				[6] OriginalCalledPartyID 	 OPTIONAL,
	prefix						[7] Digits 	OPTIONAL,
	redirectingPartyID				[8] RedirectingPartyID 	OPTIONAL,
	redirectionInformation				[9] RedirectionInformation	OPTIONAL,
	routeList						[10] RouteList 	OPTIONAL,
	travellingClassMark				[11] TravellingClassMark 	OPTIONAL,
	extensions					[12]  Extensions  	OPTIONAL,
	featureCode					[13] FeatureCode 	OPTIONAL,
	accessCode					[14] AccessCode 	OPTIONAL,
	carrier						[15] Carrier 	OPTIONAL,
	componentType				[16] ComponentType	OPTIONAL,
	component					[17] Component	OPTIONAL,
	componentCorrelationID			[18] ComponentCorrelationID	OPTIONAL
	}

-- For the OPTIONAL parameters, refer to the trigger detection point processing rules 
-- to specify when these parameters are included in the message.

-- Direction: SCF ->  SSF, Timer: Tai    
-- This operation is used to request the SSF to perform the originating basic call processing actions 
-- to analyse destination information that is either collected from a calling party or provided by the SCF 
-- (e.g. for number translation). This includes actions to validate the information according to an office 
-- or customized dialing plan, and if valid, to determine call termination information, to include the called 
-- party address, the type of call (e.g. intra-network or inter-network), and carrier (if inter-network). 
-- If the called party is not served by the SSF, the SSF also determines a route index based on the called 
-- party address and class of service, where the route index points to a list of outgoing trunk groups.

AnalyseInformationArg  ::= SEQUENCE {
	destinationRoutingAddress			[0] DestinationRoutingAddress ,
	alertingPattern				[1] AlertingPattern		OPTIONAL,
		iSDNAccessRelatedInformation	[2] ISDNAccessRelatedInformation  	OPTIONAL,
	originalCalledPartyID				[3] OriginalCalledPartyID 	OPTIONAL,
	extensions					[4] Extensions  		OPTIONAL,
	callingPartyNumber				[5] CallingPartyNumber  	OPTIONAL,
	callingPartysCategory				[6] CallingPartysCategory	OPTIONAL,
	calledPartyNumber				[7] CalledPartyNumber  	OPTIONAL,
	chargeNumber				[8] ChargeNumber 	 OPTIONAL,
	travellingClassMark				[9] TravellingClassMark 	OPTIONAL,
	carrier						[10] Carrier 		OPTIONAL,
	serviceInteractionIndicators		[11] ServiceInteractionIndicators 	OPTIONAL,
	iNServiceCompatibilityResponse	[12] INServiceCompatibilityResponse	OPTIONAL,
	forwardGVNS					[13] ForwardGVNS 	 OPTIONAL,
	backwardGVNS				[14] BackwardGVNS 	OPTIONAL,
	serviceInteractionIndicatorsTwo		[15] ServiceInteractionIndicatorsTwo 	OPTIONAL,
	correlationID					[16] CorrelationID 	 OPTIONAL,
	scfID						[17] ScfID 		OPTIONAL,
	callSegmentID				[18] CallSegmentID  	OPTIONAL,
	legToBeCreated				[19] LegID		OPTIONAL
	}

-- Direction: SCF ->  SSF, Timer: Tac    
-- This operation is used  for  interacting  from  the SCF with the SSF charging mechanisms.
-- The ApplyChargingReport operation provides the  feedback from the SSF to  the SCF.
-- This operation is can also be used to instruct the SSF to release the call regarding some condition.

ApplyChargingArg  ::= SEQUENCE {
	aChBillingChargingCharacteristics			[0] AChBillingChargingCharacteristics 
											,
	partyToCharge						[2] LegID	OPTIONAL,
	extensions							[3] Extensions   	OPTIONAL,
	releaseIndication						[4] BOOLEAN	OPTIONAL,
	releaseCause							[5] Cause 	OPTIONAL

	}
-- The TAG value 1 should not be used  for future extensions (used in CS-1 by regions).
-- The partyToCharge parameter indicates the party in the call to which the ApplyCharging operation
-- should be applied. If it is not present, then it is applied to the A-party
-- The releaseIndicator shall be present and set to TRUE if the release condition is specified in the 
-- aCHBillingCharacteristics parameter.



-- Direction: SSF ->  SCF, Timer: Tacr  
-- This operation is used  by the SSF to  report to the SCF the occurrence of a specific charging event 
-- as requested  by the SCF using the ApplyCharging operation.     

ApplyChargingReportArg ::= CallResult 
-- Note: When the SSF sends the ApplyChargingReport operation as the last event from the Call Segment, the 
--    lastEventIndicator parameter such as the CallInformationReport operation is needed for indicating whether 
--    the event is last to the SCF.  However, because there is no consideration for the parameter expansion in the 
--   CS-1, this parameter cannot be added.  There are two alternatives for the solution.  One is to be included 
--    into the CallResult parameter.  And the other is to specify a new operation with this parameter.  The latter is 
--    ffs.


-- Direction: SSF  -> SCF or SRF  -> SCF, Timer: Tari
-- This operation is used when there is an assist or a hand-off procedure and may be sent by the SSF
-- or SRF to the SCF. This operation is sent by the assisting SSF to SCF, when the initiating SSF has
-- set up a connection to the SRF or to the assisting SSF as a result of receiving an EstablishTemporaryConnection
-- or Connect/SelectRoute operation (in the case of hand-off) from the SCF.

AssistRequestInstructionsArg  ::= SEQUENCE {
	correlationID		[0] CorrelationID ,
	iPAvailable		[1] IPAvailable 		OPTIONAL,
	iPSSPCapabilities	[2] IPSSPCapabilities 	OPTIONAL,
	extensions		[3]  Extensions  		OPTIONAL
	}
-- OPTIONAL denotes network operator specific use. The value of the correlationID may be the 
-- Called Party Number supplied by the initiating SSF.

--	Direction: SCF -> SSF. Timer: Tatr
--	This operation is used to request the SSF to resume terminating call processing action at the
--	Authorize_Termination PIC of the call based on the information received from the SCF.
AuthorizeTerminationArg  ::= SEQUENCE {
	alertingPattern					[0] AlertingPattern	OPTIONAL,
	callingPartyNumber					[1] CallingPartyNumber 	OPTIONAL,
	destinationNumberRoutingAddress		[2] CalledPartyNumber 	OPTIONAL,
	displayInformation					[3] DisplayInformation 	OPTIONAL,
	iSDNAccessRelatedInformation			[4] ISDNAccessRelatedInformation 												OPTIONAL,
	originalCalledPartyID					[5] OriginalCalledPartyID  	OPTIONAL,
	travellingClassMark					[6] TravellingClassMark 	OPTIONAL,
	extensions						[7]  Extensions  	OPTIONAL,
	iNServiceCompatibilityResponse		[8] INServiceCompatibilityResponse												OPTIONAL,
	forwardGVNS						[9] ForwardGVNS 	OPTIONAL,
	backwardGVNS					[10] BackwardGVNS 	OPTIONAL,
	legID							[11] LegID	OPTIONAL
	}
-- OPTIONAL parameters are only provided if modifications are desired to basic call processing values.



-- Direction: SCF ->  SSF, Timer: Tcg   
-- This operation is used to request the SSF  to reduce the rate at which specific service requests are sent to 
-- the  SCF.  Use of this operation by the SCF to gap queries and updates at the SDF is outside the scope of this capability set .

CallGapArg  ::= SEQUENCE {
	gapCriteria					[0] GapCriteria ,
	gapIndicators					[1] GapIndicators,
	controlType					[2] ControlType	OPTIONAL,
	gapTreatment				[3] GapTreatment 	OPTIONAL,
	extensions					[4]  Extensions  	OPTIONAL
	}
-- OPTIONAL denotes network operator optional. If gapTreatment is not present, the SSF will use 
-- a default treatment depending on network operator implementation.

-- Direction: SSF ->  SCF, Timer: Tcirp    
-- This operation is used to send specific call information for a single call to the SCF as requested by the SCF 
-- in a previous CallInformationRequest.

CallInformationReportArg  ::= SEQUENCE {
	requestedInformationList			[0] RequestedInformationList ,
	correlationID					[1] CorrelationID 	OPTIONAL,
	extensions					[2] Extensions  	OPTIONAL,
	legID						[3] LegID		OPTIONAL,
	lastEventIndicator				[4] BOOLEAN 		DEFAULT  FALSE
	}
-- OPTIONAL denotes network operator optional.
-- The lastEventIndicator parameter is set with 'TRUE' when the report is last in the Call Segment. 
-- In the CS-1, the lastEventIndicator should not be sent, and the meaning of DEFAULT is not applied.  The SCF 
-- must decide whether the report is last without this parameter. 

-- Direction: SCF ->  SSF, Timer: Tcirq    
-- This operation is used to request the SSF to  record specific information about a single call and report it to 
-- the SCF (with a CallInformationReport operation). 

CallInformationRequestArg  ::= SEQUENCE {
	requestedInformationTypeList			[0] RequestedInformationTypeList,
	correlationID						[1] CorrelationID 	OPTIONAL,
	extensions						[2] Extensions  	OPTIONAL,
	legID							[3] LegID	OPTIONAL
	}
-- OPTIONAL denotes network operator optional .

-- Direction: SCF ->  SSF, or SCF  -> SRF, Timer:  Tcan 
-- This operation cancels the correlated previous operation or all previous requests
-- This operation can also be used to cancel all outstanding requests and enable the state machine (SSF)
-- to go to idle. In  this case the Cancel operation  does not specify any specific operation to be cancelled.
-- For the SCF-SRF operations that can be cancelled, refer to Q.1238.3 

CancelArg  ::= CHOICE {
	invokeID					[0] InvokeId,
	allRequests				[1] NULL,
	callSegmentToCancel			[2] SEQUENCE {
			invokeID				[0] InvokeId,
			callSegmentID			[1] CallSegmentID 
			},
	allRequestsForCallSegment	[3] CallSegmentID 

	}
-- The InvokeID has the same value as that which was used for the SCF-SRF  operation, i.e.  is used to identify 
--  the correlated previous SCF-SRF operation to be canccelled.

-- Direction: SCF ->  SSF, Timer:  Tcsr  
-- This operation cancels the following processes: RequestFirstStatusMatchReport and 
-- RequestEveryStatusChangeReport.

CancelStatusReportRequestArg  ::= SEQUENCE {
	resourceID	[0] ResourceID 	OPTIONAL,
	extensions	[1] Extensions 	OPTIONAL
	}

-- Direction: SSF ->  SCF, Timer: Tcdi    
-- This operation is used to indicate availability of complete initial information package/dialing string from 
-- originating party. (This event may have already occurred in the case of en bloc signaling, in which case 
-- the waiting duration in this PIC is zero.) (DP  - Collected_Info). For additional information on this operation 
-- and its use with open numbering plans, refer to clause 24. 

CollectedInformationArg  ::= SEQUENCE {
	dpSpecificCommonParameters		[0] DpSpecificCommonParameters ,
	dialledDigits					[1] CalledPartyNumber 	OPTIONAL,
	callingPartyBusinessGroupID		[2] CallingPartyBusinessGroupID	OPTIONAL,
	callingPartySubaddress			[3] CallingPartySubaddress 	OPTIONAL,
	callingFacilityGroup				[4] FacilityGroup	OPTIONAL,
	callingFacilityGroupMember		[5] FacilityGroupMember	OPTIONAL,
	originalCalledPartyID				[6] OriginalCalledPartyID 	OPTIONAL,
	prefix						[7] Digits 	OPTIONAL,
	redirectingPartyID				[8] RedirectingPartyID 	OPTIONAL,
	redirectionInformation				[9] RedirectionInformation	OPTIONAL,
	travellingClassMark				[10] TravellingClassMark 	OPTIONAL,
	extensions					[11] Extensions  	OPTIONAL,
	featureCode						[12] FeatureCode 	OPTIONAL,
	accessCode						[13] AccessCode 	OPTIONAL,
	carrier							[14] Carrier 	OPTIONAL,
	componentType				[15] ComponentType	OPTIONAL,
	component						[16] Component	OPTIONAL,
	componentCorrelationID			[17] ComponentCorrelationID	OPTIONAL
	}

-- For the OPTIONAL parameters, refer to clause 2.1.2 for the trigger detection point processing rules to specify 
-- when these parameters are included in the message.

-- Direction: SCF ->  SSF, Timer: Tci   
-- This operation is used to request the SSF to perform the originating basic call processing actions to prompt 
-- a calling party for destination information, then collect destination information according to a specified 
-- numbering plan (e.g. for virtual private networks).

CollectInformationArg  ::= SEQUENCE {
	alertingPattern				[0] AlertingPattern		OPTIONAL,
	numberingPlan				[1] NumberingPlan 		OPTIONAL,
	originalCalledPartyID				[2] OriginalCalledPartyID  	OPTIONAL,
	travellingClassMark				[3] TravellingClassMark 	OPTIONAL,
	extensions					[4] Extensions  		OPTIONAL,
	callingPartyNumber				[5] CallingPartyNumber 	OPTIONAL,
	dialledDigits					[6] CalledPartyNumber 	OPTIONAL,
	serviceInteractionIndicators		[7] ServiceInteractionIndicators 	OPTIONAL,
	iNServiceCompatibilityResponse	[8] INServiceCompatibilityResponse 	OPTIONAL,
	forwardGVNS					[9] ForwardGVNS 	OPTIONAL,
	backwardGVNS				[10] BackwardGVNS 	OPTIONAL,
	serviceInteractionIndicatorsTwo		[11] ServiceInteractionIndicatorsTwo 	OPTIONAL,
	callSegmentID				[12] CallSegmentID 	OPTIONAL,
	legToBeCreated				[13] LegID		OPTIONAL
	}


-- Direction: SCF ->  SSF, Timer: Tcon   
-- This operation is used to request the SSF to perform the call processing actions to route or forward a call to 
-- a specified destination. To do so, the SSF may or may not use destination information from the calling party 
-- (e.g. dialed digits) and existing call setup information (e.g. route index to a list of trunk groups), depending on 
-- the information provided by the SCF.
-- 	- When address information is only included in the Connect operation, call processing resumes at PIC3 in 
--	   the O-BCSM. 
-- 	- When address information and routing information is included, call processing resumes at PIC4.

ConnectArg  ::= SEQUENCE {
	destinationRoutingAddress			[0] DestinationRoutingAddress ,
	alertingPattern				[1] AlertingPattern		OPTIONAL,
	correlationID					[2] CorrelationID 	OPTIONAL,
	cutAndPaste					[3] CutAndPaste		OPTIONAL,
	forwardingCondition 				[4] ForwardingCondition	OPTIONAL,
	iSDNAccessRelatedInformation		[5] ISDNAccessRelatedInformation 	OPTIONAL,
	originalCalledPartyID				[6] OriginalCalledPartyID 	OPTIONAL,
	routeList						[7] RouteList 		OPTIONAL,
	scfID						[8] ScfID 		OPTIONAL,
	travellingClassMark				[9] TravellingClassMark 	OPTIONAL,
	extensions					[10] Extensions  		OPTIONAL,
	carrier						[11] Carrier 		OPTIONAL,
	serviceInteractionIndicators		[26] ServiceInteractionIndicators 	OPTIONAL,
	callingPartyNumber				[27] CallingPartyNumber 	OPTIONAL,
	callingPartysCategory				[28] CallingPartysCategory	OPTIONAL,
	redirectingPartyID				[29] RedirectingPartyID 	OPTIONAL,
	redirectionInformation				[30] RedirectionInformation 	OPTIONAL,
	displayInformation				[12] DisplayInformation 	OPTIONAL,
	forwardCallIndicators				[13] ForwardCallIndicators	OPTIONAL,
	genericNumbers				[14] GenericNumbers 	OPTIONAL,
	serviceInteractionIndicatorsTwo		[15] ServiceInteractionIndicatorsTwo	OPTIONAL,
	iNServiceCompatibilityResponse	[16] INServiceCompatibilityResponse	OPTIONAL,
	forwardGVNS					[17] ForwardGVNS 	OPTIONAL,
	backwardGVNS				[18] BackwardGVNS 	OPTIONAL,
	chargeNumber				[19] ChargeNumber 	 OPTIONAL,
	callSegmentID				[20] CallSegmentID 	 OPTIONAL,
	legToBeCreated				[21] LegID		OPTIONAL,
	sDSSinformation				[22] SDSSinformation 	   OPTIONAL,
	calledDirectoryNumber			[23] CalledDirectoryNumber  	OPTIONAL,
	aTMTrafficDescriptor				[24] ATMTrafficDescriptor  	  OPTIONAL,
	bearerCapability				[25] BearerCapability  	OPTIONAL,
	qoSParameter				[31] QoSParameter 	    OPTIONAL
		}

-- For alerting pattern, OPTIONAL denotes that this parameter only applies if SSF is the terminating local 
-- exchange for the subscriber.

-- Direction: SCF ->  SSF, Timer: Tctr    
-- This operation is used to connect a call from the SSP to the physical entity containing the SRF. 

ConnectToResourceArg  ::= SEQUENCE {
	resourceAddress	CHOICE {
		ipRoutingAddress			[0] IPRoutingAddress ,
		legID				[1] LegID,
		ipAddressAndLegID		[2] SEQUENCE {
			 ipRoutingAddress				[0] IPRoutingAddress ,
			 legID						[1] LegID
			 },
		nnone				[3] NULL,
		callSegmentID			[5] CallSegmentID  ,
		ipAddressAndCallSegment	[6] SEQUENCE {
			 ipRoutingAddress				[0] IPRoutingAddress ,
			 callSegmentID					[1] CallSegmentID 
			 }
		},
	extensions				[4] Extensions  		OPTIONAL,
	serviceInteractionIndicators	[30] ServiceInteractionIndicators 	OPTIONAL,
	serviceInteractionIndicatorsTwo	[7] ServiceInteractionIndicatorsTwo	OPTIONAL,
		uSIServiceIndicator		[35] USIServiceIndicator 	OPTIONAL,
	uSIInformation			[36] USIInformation 			OPTIONAL


	}

-- Direction: SCF ->  SSF, Timer: Tcue    
-- This operation is used to request the SSF to proceed with call processing at the DP at which it 
-- previously suspended call processing to await SCF instructions (i.e. proceed to the next point 
-- in call in the BCSM). The SSF continues call processing without substituting new data from SCF.
-- This operation is not valid for a single call segment CSA with more than 2 legs or a multi call segment CSA.
-- Direction: SCF ->  SSF, Timer: Tcwa    
-- This operation is used to request the SSF to proceed with call processing at the DP a which it previously
-- suspended call processing to await SCF instructions. 
-- It is also used to provide additional service related information to a User (Called Party or Calling Party) whilst
-- the call processing proceeds.

ContinueWithArgumentArg  ::= SEQUENCE {
	legorCSID	CHOICE{
		legID					[0] LegID,
		csID							[9] CallSegmentID }                DEFAULT legID:sendingSideID:leg1,
	alertingPattern				[1] AlertingPattern	OPTIONAL,
	genericName					[2] GenericName 	OPTIONAL,
	iNServiceCompatibilityResponse	[3] INServiceCompatibilityResponse	OPTIONAL,
	forwardGVNS					[4] ForwardGVNS 	OPTIONAL,
	backwardGVNS				[5] BackwardGVNS 	OPTIONAL,
	extensions					[6]  Extensions  	OPTIONAL,
	serviceInteractionIndicatorsTwo		[7] ServiceInteractionIndicatorsTwo    OPTIONAL,
	sDSSinformation				[8] SDSSinformation  	    OPTIONAL
	}

-- Direction SCF -> SSF, Timer Tcsa 
-- This operation is used to create a new CSA. The new CSA will not contain any Call Segments after creation.
-- The SSF is responsible for specifying a new CSA identifier for the created CSA which is unique within
--  the SSF.

CreateCallSegmentAssociationArg  ::= SEQUENCE {
	extensions				[0] Extensions  OPTIONAL
	}

CreateCallSegmentAssociationResultArg  ::= SEQUENCE {
	newCallSegmentAssociation	[0] CSAID 
	}

-- Direction: SCF  ->  SSF,  Class 1, Timer: Tcrt
--  This operation is used by the SCF outside the context of  a call  to create a new trigger detection point in the SSF/CCF by downloading trigger data (e.g. triggering criteria, ServiceKey, SCF address,....) or to remove an existing trigger .

	
CreateOrRemoveTriggerDataArg   ::= SEQUENCE {
	createOrRemove		[ 0 ] CreateOrRemoveIndicator, -- DEFAULT create,
	dPName            	[1] EventTypeBCSM		OPTIONAL,
	triggerDPType              	[2] TriggerDPType, -- DEFAULT tdp-r,	
	serviceKey                   	[3]  ServiceKey			OPTIONAL,
	profileIdentifier          	[4] ProfileIdentifier		OPTIONAL,
	triggerData                  	[5] TriggerData             		                                   OPTIONAL,
	defaultFaultHandling 	[6] DefaultFaultHandling          	                      OPTIONAL,	
tDPIdentifier             	[7] TDPIdentifier                   	                            OPTIONAL,
	extensions                     [8] Extensions      		  OPTIONAL
		}

CreateOrRemoveTriggerDataResultArg   ::= SEQUENCE {
	triggerStatus            [0] TriggerStatus,
	tDPIdentifier             [1] TDPIdentifier ,                                               
	registratorIdentifier [2] RegistratorIdentifier		 OPTIONAL,
	extensions               [3]  Extensions          	        	         OPTIONAL
	
	}



-- Direction: SCF ->  SSF, Timer: Tdfc    
-- This operation is used to disconnect a forward temporary connection or a connection to a resource. 


-- Direction: SCF ->  SSF, Timer: Tdfcwa    
-- This operation is used to disconnect a forward temporary connection or a connection to a resource. 

DisconnectForwardConnectionWithArgumentArg  ::= SEQUENCE {

	partyToDisconnect	CHOICE {
			legID			[0] LegID,
			callSegmentID		[1] CallSegmentID 
			},
	extensions				[2] Extensions  	OPTIONAL,
	uSIServiceIndicator		[3] USIServiceIndicator 	OPTIONAL,
	uSIInformation			[4] USIInformation 			OPTIONAL

	}

--	Direction: SCF -> SSF. Timer: T dl
--	This operation  is issued by the SCF  to release a specific leg associated with the call and retain any
--	other legs not specified in the DisconnectLeg. Any leg may be disconnected, including the controlling
--	leg, without completely releasing all legs.


DisconnectLegArg  ::= SEQUENCE {
	legToBeReleased	[0] LegID,
	releaseCause		[1] Cause 	OPTIONAL,
	extensions		[2] Extensions 	OPTIONAL
	}



-- Direction SSF -> SCF, Timer: Ter
-- This operation is used by SSF to inform the SCF of an error/exception

EntityReleasedArg   ::= CHOICE {
	cSFailure	[0] SEQUENCE{
			callSegmentID	[0] CallSegmentID ,
			reason			[1] Reason 	OPTIONAL,
			cause			[2] Cause 	OPTIONAL
			},
	bCSMFailure	[1] SEQUENCE{
			legID			[0] LegID,
			reason			[1] Reason 	OPTIONAL,
			cause			[2] Cause 	OPTIONAL
			}
	}

-- Direction: SCF ->  SSF, Timer: Tetc    
-- This operation is used to create a connection to a resource for a limited period of time 
-- (e.g. to play an announcement, to collect user information); it implies the use of the assist 
-- procedure.

EstablishTemporaryConnectionArg  ::= SEQUENCE {
	assistingSSPIPRoutingAddress	[0] AssistingSSPIPRoutingAddress ,
	correlationID				[1] CorrelationID 		OPTIONAL,
	partyToConnect	CHOICE {
					legID			[2] LegID,
					callSegmentID	[7] CallSegmentID 
									}				OPTIONAL,
	scfID						[3] ScfID 			OPTIONAL,
	extensions					[4] Extensions  			OPTIONAL,
	carrier						[5] Carrier 		OPTIONAL,
	serviceInteractionIndicators	[30] ServiceInteractionIndicators 	OPTIONAL,
	serviceInteractionIndicatorsTwo	[6] ServiceInteractionIndicatorsTwo	OPTIONAL
	}

-- Direction: SSF ->  SCF, Timer: Tenc  
-- This operation is used  by the SSF to  report to the SCF  the occurence of a specific charging event  
-- type as  previously requested  by the SCF in a RequestNotificationChargingEvent operation. 

EventNotificationChargingArg  ::= SEQUENCE {
	eventTypeCharging				[0] EventTypeCharging ,
	eventSpecificInformationCharging	[1] EventSpecificInformationCharging 	OPTIONAL,
	legID						[2] LegID	OPTIONAL,
	extensions					[3]  Extensions  	OPTIONAL,
	monitorMode						[30] MonitorMode   -- DEFAULT  	notifyAndContinue
	}
-- OPTIONAL denotes network operator specific use.

-- Direction: SSF  -> SCF, Timer: Terb 
-- This operation is used to notify the SCF of a call-related event (e.g. BCSM events such as busy or 
-- no answer) previously requested by the SCF in a RequestReportBCSMEvent operation.

EventReportBCSMArg  ::= SEQUENCE {
	eventTypeBCSM				[0] EventTypeBCSM,
	bcsmEventCorrelationID			[1] CorrelationID 		OPTIONAL,
	eventSpecificInformationBCSM		[2] EventSpecificInformationBCSM 														OPTIONAL,
	legID							[3] LegID			OPTIONAL,
	miscCallInfo					[4] MiscCallInfo	DEFAULT
												{messageType request},
	extensions						[5]  Extensions  			OPTIONAL,
	componentType				[6] ComponentType		OPTIONAL,
	component							[7] Component		OPTIONAL,
	componentCorrelationID			[8] ComponentCorrelationID	OPTIONAL
	}


--	SSF->SCF, Timer: Terf
-- This operation is issued by the SSF  to report the SCF the event, that was previously requested by the 
-- SCF, the CCF/SSF receives a DSS1 message which contains a FACILITY IE.   Criteria for the report, like 
-- reception of the ReturnResult which is specified with ComponentType, is optionally checked 
-- before issuing this operation.  

EventReportFacilityArg  ::= SEQUENCE{
	componentType				[0] ComponentType 	OPTIONAL,
	component					[1] Component	OPTIONAL,
	legID   						[2] LegID		OPTIONAL,
	componentCorrelationID			[3]  ComponentCorrelationID	OPTIONAL,
	extensions					[4]   Extensions 	OPTIONAL
	}

--	Direction: SSF -> SCF. Timer: Tfs
--	This operation is used for indication of a call termination attempt from the terminating half BCSM. (DP -
--	Facility_Selected_And_Available). 

FacilitySelectedAndAvailableArg  ::= SEQUENCE {
	dpSpecificCommonParameters 		[0] DpSpecificCommonParameters ,
	calledPartyBusinessGroupID		[1] CalledPartyBusinessGroupID	OPTIONAL,
	calledPartySubaddress			[2] CalledPartySubaddress 	OPTIONAL,
	callingPartyBusinessGroupID		[3] CallingPartyBusinessGroupID	OPTIONAL,
	callingPartyNumber				[4] CallingPartyNumber 	OPTIONAL,
	originalCalledPartyID				[5] OriginalCalledPartyID 	OPTIONAL,
	redirectingPartyID				[6] RedirectingPartyID 	OPTIONAL,
	redirectionInformation				[7] RedirectionInformation	OPTIONAL,
	routeList						[8] RouteList 	OPTIONAL,
	travellingClassMark				[9] TravellingClassMark 	OPTIONAL,
	extensions					[10]   Extensions  		OPTIONAL,
	componentType				[11] ComponentType	OPTIONAL,
	component						[12] Component	OPTIONAL,
	componentCorrelationID			[13] ComponentCorrelationID	OPTIONAL
	}

-- For the OPTIONAL parameters, refer to clause 2 for the trigger detection point processing rules 
-- to specify when these parameters are included in the message.

-- Direction: SCF ->  SSF, Timer: Tfci  
-- This operation is used to request the SSF  to generate,  register a call record or to include some information
-- in the default call  record. The registered call record is intended for off line charging of the call.    

FurnishChargingInformationArg  ::= FCIBillingChargingCharacteristics 

-- Direction: SCF -> SSF, Timer: Thcn 
-- This operation is used to provide the capability of queueing a call during the setup phase (e.g. to provide 
-- a call completion to busy, the call would be queued until the destination becomes free).

HoldCallInNetworkArg ::= CHOICE {
	holdcause	[0] HoldCause,
	empty		[1] NULL
	}
-- holdcause is optional and denotes network operator specific use.

-- Direction: SSF ->  SCF, Timer: Tidp 
-- This operation is used after a TDP to indicate request for service.

InitialDPArg  ::= SEQUENCE {
	serviceKey				[0] ServiceKey			OPTIONAL,
	dialledDigits				[1] CalledPartyNumber 			OPTIONAL,
	calledPartyNumber			[2] CalledPartyNumber 			OPTIONAL,
	callingPartyNumber			[3] CallingPartyNumber 			OPTIONAL,
	callingPartyBusinessGroupID	[4] CallingPartyBusinessGroupID	OPTIONAL,
	callingPartysCategory			[5] CallingPartysCategory			OPTIONAL,
	callingPartySubaddress		[6] CallingPartySubaddress		OPTIONAL,
	cGEncountered			[7] CGEncountered			OPTIONAL,
	iPSSPCapabilities			[8] IPSSPCapabilities 			OPTIONAL,
	iPAvailable				[9] IPAvailable 			OPTIONAL,
	locationNumber			[10] LocationNumber 			OPTIONAL,
	miscCallInfo				[11] MiscCallInfo			OPTIONAL,
	originalCalledPartyID			[12] OriginalCalledPartyID 		OPTIONAL,
	serviceProfileIdentifier			[13] ServiceProfileIdentifier			OPTIONAL,
	terminalType				[14] TerminalType			OPTIONAL,
	extensions				[15]  Extensions  			OPTIONAL,
	triggerType				[16] TriggerType			OPTIONAL,
	highLayerCompatibility		[23] HighLayerCompatibility			OPTIONAL,
	serviceInteractionIndicators	[24] ServiceInteractionIndicators  	OPTIONAL,
	additionalCallingPartyNumber	[25] AdditionalCallingPartyNumber 	OPTIONAL,
	forwardCallIndicators			[26] ForwardCallIndicators			OPTIONAL,
	bearerCapability			[27] BearerCapability 			OPTIONAL,
	eventTypeBCSM			[28] EventTypeBCSM			OPTIONAL,
	redirectingPartyID			[29] RedirectingPartyID 			OPTIONAL,
	redirectionInformation			[30] RedirectionInformation			OPTIONAL,
	cause					[17] Cause 			OPTIONAL,
	componentType			[18] ComponentType			OPTIONAL,
	component					[19] Component			OPTIONAL,
	componentCorrelationID		[20] ComponentCorrelationID		OPTIONAL,
	iSDNAccessRelatedInformation	[21] ISDNAccessRelatedInformation 	OPTIONAL,
	iNServiceCompatibilityIndication	[22] INServiceCompatibilityIndication 															OPTIONAL,
	genericNumbers			[31] GenericNumbers 			OPTIONAL,
	serviceInteractionIndicatorsTwo	[32] ServiceInteractionIndicatorsTwo	OPTIONAL,
	forwardGVNS				[33] ForwardGVNS 			OPTIONAL,
	createdCallSegmentAssociation	[34] CSAID 			OPTIONAL,
	uSIServiceIndicator			[35] USIServiceIndicator 		OPTIONAL,
	uSIInformation			[36] USIInformation 			OPTIONAL,
	carrier					[37] Carrier 			OPTIONAL,
	cCSS					[38] CCSS		OPTIONAL,
	vPNIndicator				[39] VPNIndicator   	OPTIONAL ,
	cNInfo					[40] OCTET STRING(SIZE(1..13)) 	OPTIONAL ,
	callReference				[41] CallReference	OPTIONAL,
	routingNumber			[42] RoutingNumber 			OPTIONAL,
	aTMTrafficDescriptor			[43] ATMTrafficDescriptor 	OPTIONAL,
	qoSParameter			[45] QoSParameter 	OPTIONAL,
	callingGeodeticLocation		[46] CallingGeodeticLocation 	OPTIONAL
	}

-- OPTIONAL for iPSSPCapabilities, iPAvailable, cGEncountered, and miscCallInfo denotes network 
-- operator specific use.
-- OPTIONAL for dialledDigits, callingPartyNumber, and callingPartysCategory refer to clause 2 for the trigger 
-- detection point processing rules to specify when these parameters are included in the message.
-- OPTIONAL for terminalType indicates that this parameter applies only at originating or terminating 
-- local exchanges if the SSF has this information.
-- encoding of cNInfo  is similar to the NNI specific information  in  the APP parameter in Q.765.1
--first octet contains Q.765.1 CNID indicator, only bit 5 and 6 are significant,This is followed by  zero to 12 octets 
--that contains the Q.765.1 CNID parameter, i.e. the Corporate Telecommunications Network  Identifier , if  present..

-- Direction: SCF ->  SSF, Timer: Tica 
-- This operation is used to request the SSF to create a new call to one call  party using address 
-- information provided by the SCF. 

InitiateCallAttemptArg  ::= SEQUENCE {
	destinationRoutingAddress		[0] DestinationRoutingAddress ,
	alertingPattern			[1] AlertingPattern		OPTIONAL,
	iSDNAccessRelatedInformation	[2] ISDNAccessRelatedInformation 	OPTIONAL,
	travellingClassMark			[3] TravellingClassMark 	OPTIONAL,
	extensions				[4]  Extensions  			OPTIONAL,
	serviceInteractionIndicators	[29] ServiceInteractionIndicators 	OPTIONAL,
	callingPartyNumber			[30] CallingPartyNumber 	OPTIONAL,
	legToBeCreated			[5] LegID 	DEFAULT 	 sendingSideID:leg1,
	newCallSegment			[6] CallSegmentID  DEFAULT initialCallSegment,
	iNServiceCompatibilityResponse	[7] INServiceCompatibilityResponse	OPTIONAL,
	serviceInteractionIndicatorsTwo	[8] ServiceInteractionIndicatorsTwo	OPTIONAL,
	correlationID				[9] CorrelationID 		OPTIONAL,
	scfID					[10] ScfID 		OPTIONAL,
	carrier					[11] Carrier 		OPTIONAL,
	callReference				[12] CallReference  		OPTIONAL,
	calledDirectoryNumber		[13] CalledDirectoryNumber  	OPTIONAL

	}

-- Direction: SCF  ->  SSF,  Class 1, Timer: Tmtd
--  This operation is used to activate, deactivate or retrieve
-- the status of one or several trigger detection point linked to a subscriber rofile known at the switch, 
-- e.g. related to an access line.

ManageTriggerDataArg   ::= SEQUENCE {
	actionIndicator	[0] ActionIndicator,
	triggerDataIdentifier	CHOICE {
		  profileAndDP	 [1] TriggerDataIdentifier , 
				-- one trigger
		   profile           	  [5] ProfileIdentifier 
		},
	registratorIdentifier	[2]  RegistratorIdentifier  	OPTIONAL,
	extensions		[3]  Extensions 	 	OPTIONAL,
	tDPIdentifier		[4] TDPIdentifier  		OPTIONAL
	 } 



ManageTriggerDataResultArg   ::= CHOICE 
	{
	oneTriggerResult 	 SEQUENCE {
	               actionPerformed	    	 [0]  ActionPerformed,
	               extensions	   		 [1] Extensions  	OPTIONAL},   
	severalTriggerResult	 [1] SEQUENCE {
                      				results	  		   [0] TriggerResults ,
	                	 extensions	  	   [1] Extensions 	OPTIONAL  }   
	}


--	Direction: SCF -> SSF. Timer: T mc
-- This operation  is issued by the SCF  to merge two associated CSs , into one CS .

MergeCallSegmentsArg  ::= SEQUENCE {
	sourceCallSegment			[0] CallSegmentID ,
	targetCallSegment			[1] CallSegmentID  DEFAULT initialCallSegment,
	extensions				[2]  Extensions 	OPTIONAL
	}

--  Direction: SCF -> SSF, Timer Tmcs 
-- This operation moves a CS from the source CSA to the the target CSA
MoveCallSegmentsArg  ::= SEQUENCE {
	targetCallSegmentAssociation	[0] CSAID ,  

	callSegments					[1] SEQUENCE SIZE (1..numOfCSs)
 OF SEQUENCE {
		sourceCallSegment			[0] CallSegmentID  	DEFAULT initialCallSegment,
		newCallSegment				[1] CallSegmentID 
		},
	legs						[2] ExportLegsType,
	extensions				[3]  Extensions 	OPTIONAL
	}

-- Direction : SCF  ->SSF, Timer: T ml
-- This operation is issued by the SCF to move a leg from one CS to another with which it is associated.

MoveLegArg  ::=SEQUENCE {
	legIDToMove					[0] LegID,
	targetCallSegment				[1] CallSegmentID  DEFAULT 1,
	extensions					[2]  Extensions  	OPTIONAL
	}
-- For the OPTIONAL parameters, refer to clause 2 for the trigger 
-- detection point processing rules to specify when these parameters are 
-- included in the message.

--	Direction: SSF -> SCF. Timer: T ob
-- This operation is issued by the SSF after detecting a valid trigger condition at the O_Abandon DP or to 
-- report an oAbandon event requested by the RequestReportBCSMEvent.

OAbandonArg  ::= SEQUENCE {
	dpSpecificCommonParameters 		[0] DpSpecificCommonParameters ,
	callSegmentID				[1] CallSegmentID ,
	releaseCause					[2] Cause 	OPTIONAL,
	extensions					[3]  Extensions  		OPTIONAL
	}
-- For the OPTIONAL parameters, refer to the trigger detection point rules to specify
-- when these parameter are included in the message.
-- Type definition for PointInCall isoutside the scope of this capability sets. Use of T/EDP-R is outside 
-- the scope of this capability set.


-- Direction: SSF ->  SCF, Timer: Toa 
-- This operation is used for indication from the terminating half BCSM that the call is accepted and answered 
-- by terminating party (e.g. terminating party goes offhook, Q.931 Connect message received, ISDN-UP Answer 
-- message received) (DP  - O_Answer). 

OAnswerArg  ::= SEQUENCE {
	dpSpecificCommonParameters 		[0] DpSpecificCommonParameters ,
	callingPartyBusinessGroupID		[1] CallingPartyBusinessGroupID	OPTIONAL,
	callingPartySubaddress			[2] CallingPartySubaddress 	OPTIONAL,
	callingFacilityGroup				[3] FacilityGroup	OPTIONAL,
	callingFacilityGroupMember		[4] FacilityGroupMember	OPTIONAL,
	originalCalledPartyID				[5] OriginalCalledPartyID 	OPTIONAL,
	redirectingPartyID				[6] RedirectingPartyID 	OPTIONAL,
	redirectionInformation				[7] RedirectionInformation	OPTIONAL,
	routeList						[8] RouteList 	OPTIONAL,
	travellingClassMark				[9] TravellingClassMark 	OPTIONAL,
	extensions					[10]  Extensions  		OPTIONAL
	}
-- For the OPTIONAL parameters, refer to clause 2 for the trigger detection point processing rules 
-- to specify when these parameters are included in the message.
-- Direction: SSF -> SCF, Timer: Tob 
-- This operation is used for Indication from the terminating half BCSM that the terminating party is busy 
-- (DP  - O_Called_Party_Busy). .  

OCalledPartyBusyArg  ::= SEQUENCE {
	dpSpecificCommonParameters	 	[0] DpSpecificCommonParameters ,
	busyCause					[1] Cause 	OPTIONAL,
	callingPartyBusinessGroupID		[2] CallingPartyBusinessGroupID	OPTIONAL,
	callingPartySubaddress			[3] CallingPartySubaddress 	OPTIONAL,
	callingFacilityGroup				[4] FacilityGroup	OPTIONAL,
	callingFacilityGroupMember		[5] FacilityGroupMember	OPTIONAL,
	originalCalledPartyID				[6] OriginalCalledPartyID 	OPTIONAL,
	prefix						[7] Digits 	OPTIONAL,
	redirectingPartyID				[8] RedirectingPartyID 	OPTIONAL,
	redirectionInformation				[9] RedirectionInformation	OPTIONAL,
	routeList						[10] RouteList 	OPTIONAL,
	travellingClassMark				[11] TravellingClassMark 	OPTIONAL,
	extensions					[12]  Extensions  		OPTIONAL,
	carrier						[13] Carrier 	OPTIONAL
	}
-- For the OPTIONAL parameters, refer to clause 2 for the trigger detection point processing rules 
-- to specify when these parameters are included in the message.
-- Direction: SSF ->  SCF, Timer: Tod 
-- This operation is used for a disconnect indication (e.g. onhook, Q.931 Disconnect message, SS7 Release message) 
-- is received from the originating party, or received from the terminating party via the terminating half BCSM. 
-- (DP  - O_Disconnect). . 

ODisconnectArg  ::= SEQUENCE {
	dpSpecificCommonParameters 		[0] DpSpecificCommonParameters ,
	callingPartyBusinessGroupID		[1] CallingPartyBusinessGroupID	OPTIONAL,
	callingPartySubaddress			[2] CallingPartySubaddress 	OPTIONAL,
	callingFacilityGroup				[3] FacilityGroup	OPTIONAL,
	callingFacilityGroupMember		[4] FacilityGroupMember	OPTIONAL,
	releaseCause					[5] Cause 	OPTIONAL,
	routeList						[6] RouteList 	OPTIONAL,
	extensions					[7]   Extensions  		OPTIONAL,
	carrier						[8] Carrier 	OPTIONAL,
	connectTime					[9] Integer4	OPTIONAL,
	componentType				[10] ComponentType	OPTIONAL,
	component						[11] Component	OPTIONAL,
	componentCorrelationID			[12] ComponentCorrelationID	OPTIONAL
	}

-- For the OPTIONAL parameters, refer to clause 2 for the trigger detection point processing rules 
-- to specify when these parameters are included in the message.

-- Direction: SSF ->  SCF, Timer: Tomc 
-- This operation is used to indicate a feature request is received from the originating party 
-- (e.g. hook flash, ISDN feature activation, Q.931 HOLD or RETrieve message). (DP  - O_Mid_Call). 

MidCallArg  ::= SEQUENCE {
	dpSpecificCommonParameters 		[0] DpSpecificCommonParameters ,
	calledPartyBusinessGroupID		[1] CalledPartyBusinessGroupID	OPTIONAL,
	calledPartySubaddress			[2] CalledPartySubaddress 	OPTIONAL,
	callingPartyBusinessGroupID		[3] CallingPartyBusinessGroupID	OPTIONAL,
	callingPartySubaddress			[4] CallingPartySubaddress 	OPTIONAL,
	featureRequestIndicator			[5] FeatureRequestIndicator	OPTIONAL,
	extensions					[6]   Extensions  		OPTIONAL,
	carrier						[7] Carrier 	OPTIONAL,
	componentType				[8] ComponentType	OPTIONAL,
	component						[9] Component	OPTIONAL,
	componentCorrelationID			[10] ComponentCorrelationID	OPTIONAL
	}

-- For the OPTIONAL parameters, refer to the trigger detection point processing rules 
-- to specify when these parameters are included in the message.

-- Direction: SSF ->  SCF, Timer: Tona 
-- This operation is used for indication from the terminating half BCSM that the terminating party does not 
-- answer within a specified time period (DP  - O_No_Answer). 

ONoAnswerArg  ::= SEQUENCE {
	dpSpecificCommonParameters 		[0] DpSpecificCommonParameters ,
	callingPartyBusinessGroupID		[1] CallingPartyBusinessGroupID	OPTIONAL,
	callingPartySubaddress			[2] CallingPartySubaddress 	OPTIONAL,
	callingFacilityGroup				[3] FacilityGroup	OPTIONAL,
	callingFacilityGroupMember		[4] FacilityGroupMember	OPTIONAL,
	originalCalledPartyID				[5] OriginalCalledPartyID 	OPTIONAL,
	prefix						[6] Digits 	OPTIONAL,
	redirectingPartyID				[7] RedirectingPartyID 	OPTIONAL,
	redirectionInformation				[8] RedirectionInformation	OPTIONAL,
	routeList						[9] RouteList 	OPTIONAL,
	travellingClassMark				[10] TravellingClassMark 	OPTIONAL,
	extensions					[11]  Extensions  		OPTIONAL,
	carrier						[12] Carrier 	OPTIONAL
	}
-- For the OPTIONAL parameters, refer to the trigger detection point processing rules 
-- to specify when these parameters are included in the message.

--	Direction: SSF -> SCF. Timer: Tora
-- This operation is used for indication of a call origination attempt from the originating half BCSM.
--  (DP - Origination_Attempt). 

OriginationAttemptArg  ::= SEQUENCE {
	dpSpecificCommonParameters 		[0] DpSpecificCommonParameters ,
	callingPartyBusinessGroupID		[1] CallingPartyBusinessGroupID	OPTIONAL,
	callingPartySubaddress			[2] CallingPartySubaddress 	OPTIONAL,
	callingFacilityGroup					[3] FacilityGroup	OPTIONAL,
	callingFacilityGroupMember		[4] FacilityGroupMember	OPTIONAL,
	carrier								[5] Carrier 	OPTIONAL,
	travellingClassMark					[6] TravellingClassMark 	OPTIONAL,
	extensions					[7]  Extensions  		OPTIONAL,
	componentType				[8] ComponentType	OPTIONAL,
	component						[9] Component	OPTIONAL,
	componenttCorrelationID			[10] ComponentCorrelationID	OPTIONAL
	}
-- For the OPTIONAL parameters, refer to clause 2 for the trigger detection point processing rules 
-- to specify when these parameters are included in the message.


-- Direction: SSF ->  SCF, Timer: Toaa 
-- This operation is used to Indicate the desire to place outgoing call (e.g. offhook, Q.931 Setup message, 
-- ISDN-UP IAM message) and authority/ability to place outgoing call verified (DP  - 
-- Origination_Attempt_Authorized). 

OriginationAttemptAuthorizedArg  ::= SEQUENCE {
	dpSpecificCommonParameters 		[0] DpSpecificCommonParameters ,
	dialledDigits					[1] CalledPartyNumber 	OPTIONAL,
	callingPartyBusinessGroupID		[2] CallingPartyBusinessGroupID	OPTIONAL,
	callingPartySubaddress			[3] CallingPartySubaddress 	OPTIONAL,
	callingFacilityGroup				[4] FacilityGroup	OPTIONAL,
	callingFacilityGroupMember		[5] FacilityGroupMember	OPTIONAL,
	travellingClassMark				[6] TravellingClassMark 	OPTIONAL,
	extensions					[7]  Extensions  		OPTIONAL,
	carrier						[8] Carrier 	OPTIONAL,
	componentType				[9] ComponentType	OPTIONAL,
	component						[10] Component	OPTIONAL,
	componentCorrelationID			[11] ComponentCorrelationID	OPTIONAL
	}

-- For the OPTIONAL parameters, refer to clause 2 for the trigger detection point processing rules 
-- to specify when these parameters are included in the message.

--	Direction: SSF -> SCF. Timer: T os
--	This operation is issued by the SSF after detecting a valid trigger condition at the O_Suspend DP or  to 
--	report an oSuspended event requested by the RequestReportBCSMEvent. 

OSuspendedArg  ::= SEQUENCE {
	dpSpecificCommonParameters	 	[0] DpSpecificCommonParameters ,
	legID						[1] LegID		OPTIONAL,
	extensions					[2]  Extensions 		OPTIONAL
	}
-- For the OPTIONAL parameters, refer to clause 2 for the trigger detection point processing rules 
-- to specify when these parameters are included in the message.
-- Modification to LegID is ffs. Use for T/EDP-R is ffs.


--  Direction: SCF -> SSF. Timer: T re
--  This operation is issued by the SCF to reestablish communication between the controlling leg  and the
--  (held) passive leg(s). .

ReconnectArg  ::= SEQUENCE {
	notificationDuration		[0] ApplicationTimer	OPTIONAL,
	alertingPattern		[1] AlertingPattern		OPTIONAL,
	displayInformation		[2] DisplayInformation 	OPTIONAL,
	extensions			[3]  Extensions  		OPTIONAL,
	callSegmentID		[4] CallSegmentID 	OPTIONAL
	}
-- For the OPTIONAL parameters, refer to clause 2.1.2 for the trigger detection point processing rules 
-- to specify when these parameters are included in the message.

-- Direction: SCF ->  SSF, Timer: Trc 
-- This operation is used to tear down an existing call at any phase of the call for all parties 
-- involved in the call.  

ReleaseCallArg  ::= CHOICE {
	initialCallSegment					Cause ,
	callSegmentToRelease			[1] SEQUENCE {
		callSegment				[0] INTEGER (1..numOfCSs),
		releaseCause				[1] Cause        	OPTIONAL,
		forcedRelease				[2] BOOLEAN  DEFAULT  FALSE
		},
	allCallSegments			[2] SEQUENCE {
		 releaseCause				[0] Cause  	OPTIONAL,
		timeToRelease				[1] TimerValue  	OPTIONAL,
		forcedRelease				[2] BOOLEAN  DEFAULT  FALSE
								}		
	}
-- A default cause value of decimal 31 (normal unspecified) should be coded appropriately.


-- Direction: SSF -> SCF. Timer: Tru
-- This operation is issued by the SSF in the context of the USI  feature.  It is used to report the receipt 
-- of a User to Service Information (USI)  to the SCF. 

ReportUTSIArg  ::= SEQUENCE {
	uSIServiceIndicator	[0] USIServiceIndicator ,
	legID			[1] LegID 	DEFAULT receivingSideID:leg1,
	uSIInformation	[2] USIInformation ,
	extensions			[3]  Extensions 		OPTIONAL
	}

-- Direction: SCF ->  SSF, Timer: Trcs 
-- This operation is used to request the SSF to report immediately the busy/idle status of a physical 
-- termination resource.

RequestCurrentStatusReportArg  ::= ResourceID 

RequestCurrentStatusReportResultArg  ::= SEQUENCE {
	resourceStatus	[0] ResourceStatus,
	resourceID		[1] ResourceID 	OPTIONAL,
	extensions		[2]  Extensions  	OPTIONAL
	}

-- Direction: SCF ->  SSF, Timer: Tres 
-- This operation is used to request the SSF to report every change of busy/idle status of a physical 
-- termination resource.

RequestEveryStatusChangeReportArg  ::= SEQUENCE {
	resourceID			[0] ResourceID ,	
	correlationID			[1] CorrelationID 	OPTIONAL,
	monitorDuration		[2] XDuration			OPTIONAL,
	extensions			[3]  Extensions  		OPTIONAL
	}
-- For correlationID OPTIONAL denotes network operator optional.
-- monitorDuration is required if outside the context of a call. It is not expected if we are in the context 
-- of a call, because in that case the end of the call implicitly means the end of the monitoring.

-- Direction: SCF ->  SSF, Timer: Trfs 
-- This operation is used to request the SSF to report the first change busy/idle to the specified status of 
-- a physical termination resource.

RequestFirstStatusMatchReportArg  ::= SEQUENCE {
	resourceID			[0] ResourceID 	OPTIONAL,
	resourceStatus		[1] ResourceStatus	OPTIONAL,
	correlationID			[2] CorrelationID 	OPTIONAL,
	monitorDuration		[3] XDuration			OPTIONAL,
	extensions			[4]  Extensions  		OPTIONAL,
	bearerCapability		[5] BearerCapability 	OPTIONAL
	}
-- For correlationID OPTIONAL denotes network operator optional.
-- monitorDuration is required if outside the context of a call. It is not expected if we are in the context 
-- of a call, because in that case the end of the call implicitly means the end of the monitoring.

-- Direction: SCF ->  SSF, Timer: Trnc 
-- This operation  is used by the SCF to instruct the SSF on how to manage the charging events
-- - which are received  rom other FE's and not under control of the service logic instance. 

RequestNotificationChargingEventArg  ::= SEQUENCE SIZE(1..numOfChargingEvents) OF
		 ChargingEvent 

-- Direction: SCF ->  SSF, Timer: Trrb
-- This operation is used to request the SSF to monitor for a call-related event (e.g. BCSM events such as 
-- busy or no answer), then send a notification back to the SCF when the event is detected.
-- It is proposed that Event Detection Point (EDP) processing is always initiated by RequestReportBCSMEvent
--  and the 
-- EDP may be acknowledged with either an EventReportBCSM or by a DP-specific operations:
-- NOTE - the application context should identify whether BCSM Event Handling Package
--		  is being used, or whether DP Specific Event Handling Package 
--		  is being used.
--		- for a particular IN, only one of the two alternatives identified by the respective Packages should be 
--		  selected (i.e., only one approach should be selected for a given application context).
--		- Every EDP must be explicitly armed by the SCF via a RequestReportBCSMEvent operation. No 
--		  implicit arming of EDPs at the SSF after reception of any operation (different from 
--		  RequestReportBCSMEvent) from the SCF is allowed.

RequestReportBCSMEventArg  ::= SEQUENCE {
	bcsmEvents				[0] SEQUENCE SIZE(1..numOfBCSMEvents)  OF
					   			     BCSMEvent ,
	bcsmEventCorrelationID	[1] CorrelationID 				OPTIONAL,
	extensions				[2]   Extensions  	OPTIONAL
	}
-- Indicates the BCSM related events for notification.
-- For correlationID OPTIONAL denotes network operator optional.

--	SCF->SSF, Timer: Trrfe
--	This operation is issued by the SCF to request the SSF to report the SCF the event that the CCF/SSF
-- 	receives a DSS1 message which contains a FACILITY IE during a BCSM being suspended at a DP.  

RequestReportFacilityEventArg 	::= SEQUENCE{
	componentTypes			[0] SEQUENCE SIZE(1..3) 
OF ComponentType,            -- DEFAULT {any},
	legID					[1] LegID			OPTIONAL,
	componentCorrelationID		[2] ComponentCorrelationID	OPTIONAL,
	monitorDuration			[3] XDuration,
	extensions     			[4]  Extensions 		OPTIONAL
	}
-- componentTypes specifies the component types which should be reported to the SCF.  
-- monitorDuration specifies the monitor duration.


-- Direction: SCF -> SSF. Timer: Trru
-- This operation is issued by the SCF in the context of the USI feature to request the SSF to monitor for 
-- a User to Service Information (UTSI) information element, which are received from a user.

RequestReportUTSIArg  ::= SEQUENCE {
	requestedUTSIList		[0] RequestedUTSIList ,
	extensions			[1]   Extensions 	OPTIONAL,
	legID				[2] LegID	DEFAULT sendingSideID:leg1
	}


-- Direction: SCF ->  SSF, Timer: Trt 
-- This operation is used to request the SSF to refresh an application timer in the SSF.

ResetTimerArg  ::= SEQUENCE {
	timerID			[0] TimerID			DEFAULT tssf,
	timervalue		[1] TimerValue,
	extensions		[2]  Extensions  			OPTIONAL,
	callSegmentID	[3] CallSegmentID 	OPTIONAL
	}

-- Direction: SSF ->  SCF, Timer:  Trsf 
-- This operation is used to indicate that the SSP is unable to select a route (e.g. unable to determine a 
-- correct route, no more routes on route list) or indication from the terminating half BCSM that a call 
-- cannot be presented to the terminating party (e.g. network ongestion) (DP  - Route_Select_Failure). 

RouteSelectFailureArg  ::= SEQUENCE {
	dpSpecificCommonParameters 		[0] DpSpecificCommonParameters ,
	dialledDigits					[1] CalledPartyNumber 	OPTIONAL,
	callingPartyBusinessGroupID		[2] CallingPartyBusinessGroupID	OPTIONAL,
	callingPartySubaddress			[3] CallingPartySubaddress 	OPTIONAL,
	callingFacilityGroup				[4] FacilityGroup	OPTIONAL,
	callingFacilityGroupMember		[5] FacilityGroupMember	OPTIONAL,
	failureCause					[6] Cause 	OPTIONAL,
	originalCalledPartyID				[7] OriginalCalledPartyID 	OPTIONAL,
	prefix						[8] Digits 	OPTIONAL,
	redirectingPartyID				[9] RedirectingPartyID 	OPTIONAL,
	redirectionInformation				[10] RedirectionInformation	OPTIONAL,
	routeList						[11] RouteList 	OPTIONAL,
	travellingClassMark				[12] TravellingClassMark 	OPTIONAL,
	extensions					[13]  Extensions  		OPTIONAL,
	carrier						[14] Carrier 	OPTIONAL
	}
-- For the OPTIONAL parameters, refer to clause 2 for the trigger detection point processing 
-- rules to specify when these parameters are included in the message.

-- Direction: SCF ->  SSF, Timer: Tsf 
-- This operation is used to request the SSF to perform the terminating basic call processing 
-- actions to select the terminating line if it is idle, or selects an idle line from a multi-line hunt 

-- group, or selects an idle trunk from a trunk group, as appropriate. If no idle line or trunk is 
-- available, the SSF determines that the terminating facility is busy.

SelectFacilityArg  ::= SEQUENCE {
	alertingPattern					[0] AlertingPattern	OPTIONAL,
	destinationNumberRoutingAddress		[1] CalledPartyNumber 	OPTIONAL,
	iSDNAccessRelatedInformation			[2] ISDNAccessRelatedInformation 													OPTIONAL,
	calledFacilityGroup					[3] FacilityGroup	OPTIONAL,
	calledFacilityGroupMember				[4] FacilityGroupMember	OPTIONAL,
	originalCalledPartyID					[5] OriginalCalledPartyID 	OPTIONAL,
	extensions						[6]  Extensions  		OPTIONAL,
	displayInformation					[7] DisplayInformation 	OPTIONAL,
	serviceInteractionIndicators			[8] ServiceInteractionIndicators 													OPTIONAL,
	iNServiceCompatibilityResponse		[9] INServiceCompatibilityResponse													OPTIONAL,
	forwardGVNS						[10] ForwardGVNS 	OPTIONAL,
	backwardGVNS					[11] BackwardGVNS 	OPTIONAL,
	serviceInteractionIndicatorsTwo			[12] ServiceInteractionIndicatorsTwo													OPTIONAL,
	correlationID						[13] CorrelationID 	OPTIONAL,
	scfID							[14] ScfID 		OPTIONAL,
	callSegmentID					[15] CallSegmentID 	OPTIONAL,
	legToBeCreated					[16] LegID		OPTIONAL
	}

-- OPTIONAL parameters are only provided if modifications desired to basic call processing values.

-- Direction: SCF ->  SSF, Timer: Tsr 
-- This operation is used to request the SSF to perform the originating basic call processing actions to 
-- determine routing information and select a route for a call, based either on call information available 
-- to the SSF, or on call information provided by the SCF (e.g. for alternate routing), to include the 
-- called party address, type of call, carrier, route index, and one or more alternate route indices. 
-- Based on the routing information, the SSF attempts to select a primary route for the call, and if the 
-- route is busy, attempts to select an alternate route. The SSF may fail to select a route for the call 
-- if all routes are busy.

SelectRouteArg  ::= SEQUENCE {
	destinationRoutingAddress			[0] DestinationRoutingAddress ,
	alertingPattern				[1] AlertingPattern		OPTIONAL,
	correlationID					[2] CorrelationID 	OPTIONAL,
	iSDNAccessRelatedInformation		[3] ISDNAccessRelatedInformation 													OPTIONAL,
	originalCalledPartyID				[4] OriginalCalledPartyID 	OPTIONAL,
	routeList						[5] RouteList 		OPTIONAL,
	scfID						[6] ScfID 		OPTIONAL,
	travellingClassMark				[7] TravellingClassMark 	OPTIONAL,
	extensions					[8]  Extensions  			OPTIONAL,
	carrier						[9] Carrier 		OPTIONAL,
	serviceInteractionIndicators		[10] ServiceInteractionIndicators 	OPTIONAL,
	iNServiceCompatibilityResponse	[11] INServiceCompatibilityResponse	 OPTIONAL,
	forwardGVNS					[12] ForwardGVNS 	OPTIONAL,
	backwardGVNS				[13] BackwardGVNS 	OPTIONAL,
	serviceInteractionIndicatorsTwo		[14] ServiceInteractionIndicatorsTwo	OPTIONAL,
	callSegmentID				[15] CallSegmentID 	OPTIONAL,
	legToBeCreated				[16] LegID		OPTIONAL
	}

-- OPTIONAL parameters are only provided if modifications desired to basic call processing values.
-- Direction: SCF ->  SSF, Timer: Tsci  
-- This operation is used to  instruct the SSF on the charging information to send by the SSF.
-- The charging information can either be sent back by means of signalling or internal
-- if  the SSF is located in the local exchange. In the local exchange
-- this information may be used to update the charge meter or to create a standard call record.    

SendChargingInformationArg  ::= SEQUENCE {
	sCIBillingChargingCharacteristics	[0] SCIBillingChargingCharacteristics ,
	partyToCharge		[1] LegID,
	extensions			[2]   Extensions  		OPTIONAL,
	nocharge			[3] BOOLEAN			 OPTIONAL
	}

--	SCF->SSF, Timer: Tsfi
--  This operation is issued by the SCF during a BCSM being suspended at a DP to request the CCF/SSF 
--  sending a FACILITY IE to a user with a specified DSS1 message.  

SendFacilityInformationArg  ::= SEQUENCE{
	componentType						[0] ComponentType,
	legID								[1] LegID	OPTIONAL,
	componentCorrelationID				[2] ComponentCorrelationID	OPTIONAL,
	component							[3] Component,
	callProcessingOperationCorrelationID	[4] CallProcessingOperationCorrelationID
,
										-- DEFAULT	fACility, 
	extensions							[5] Extensions 		OPTIONAL
	}
-- FACILITY information will be delivered with the specified DSS1 message.  The message is specified with the 
-- callProcessingOperationCorrelationID


-- Direction: SCF -> SSF. Timer: Tss
-- This operation is issued by the SCF in the context of the USI feature. It is used to request the SSF
-- to send a Service to User Information (USI  information) data element to the indicated user.

SendSTUIArg  ::= SEQUENCE {
	uSIServiceIndicator	[0] USIServiceIndicator ,
	legID			[1] LegID	DEFAULT sendingSideID:leg1,
	uSIInformation	[2] USIInformation ,
	extensions			[3] Extensions 		OPTIONAL
	}

-- Direction: SSF ->  SCF, Timer: Tsfr  
-- This operation is used to send back to the SCF the values of counters specified in a previous 
-- ActivateServiceFiltering operation

ServiceFilteringResponseArg  ::= SEQUENCE {
	countersValue		[0] CountersValue,
	filteringCriteria		[1] FilteringCriteria ,
	extensions			[2] Extensions  		OPTIONAL,
	responseCondition		[3] ResponseCondition	OPTIONAL
	}
-- Direction SCF-SSF, Timer Tsep
--This operation is used to request the SSF to activate/de-activate  a list of trigger for one of the parties of the call.

SetServiceProfileArg  ::= SEQUENCE {
		iNprofiles 	[0]  SEQUENCE SIZE (1..numOfINProfile)  
						OF INprofile ,
		extensions	[1] Extensions 	OPTIONAL
		}


--  Direction: SCF -> SSF. Timer: T sl
--  This operation  is issued by the SCF  to separate one joined leg from a multi-way connection
--  or  a single 2 party Call segment.

SplitLegArg  ::= SEQUENCE {
	legToBeSplit		[0] LegID,
	newCallSegment	[1] INTEGER (2..numOfCSs),
	extensions		[2] Extensions 	OPTIONAL
	}

-- Direction: SSF ->  SCF, Timer: Tsrp  
-- This operation is used as a response to RequestFirstStatusMatchReport or 
-- RequestEveryStatusChangeReport operations.

StatusReportArg  ::= SEQUENCE {
	resourceStatus	[0] ResourceStatus	OPTIONAL,
	correlationID		[1] CorrelationID 	OPTIONAL,
	resourceID		[2] ResourceID 	OPTIONAL,
	extensions		[3] Extensions  	OPTIONAL,
	reportCondition	[4] ReportCondition	OPTIONAL
	}
-- For correlationID, OPTIONAL denotes network operator optional.
-- resourceID is required when the SSF sends a report as an answer to a previous request when the 
-- correlationID was present.
-- Direction: SSF ->  SCF, Timer: Tta  
-- This operation is used to indicate that the call is accepted and answered by terminating party 
-- (e.g. terminating party goes offhook, Q.931 Connect message received, ISDN-UP Answer message 
-- received) (DP  - T_Answer). . 

TAnswerArg  ::= SEQUENCE {
	dpSpecificCommonParameters	 	[0] DpSpecificCommonParameters ,
	calledPartyBusinessGroupID		[1] CalledPartyBusinessGroupID	OPTIONAL,
	calledPartySubaddress			[2] CalledPartySubaddress 	OPTIONAL,
	calledFacilityGroup				[3] FacilityGroup	OPTIONAL,
	calledFacilityGroupMember			[4] FacilityGroupMember	OPTIONAL,
	extensions					[5] Extensions  		OPTIONAL,
	componentType				[6] ComponentType	OPTIONAL,
	component						[7] Component	OPTIONAL,
	componentCorrelationID			[8] ComponentCorrelationID	OPTIONAL
	}

-- Direction: SSF ->  SCF, Timer: Ttb  
-- This operation is used to indicate all resources in group busy (DP- TBusy). 

TBusyArg  ::= SEQUENCE {
	dpSpecificCommonParameters	[0] DpSpecificCommonParameters ,
	busyCause				[1] Cause 	OPTIONAL,
	calledPartyBusinessGroupID	[2] CalledPartyBusinessGroupID	OPTIONAL,
	calledPartySubaddress		[3] CalledPartySubaddress 	OPTIONAL,
	originalCalledPartyID			[4] OriginalCalledPartyID 	OPTIONAL,
	redirectingPartyID			[5] RedirectingPartyID 	OPTIONAL,
	redirectionInformation			[6] RedirectionInformation	OPTIONAL,
	routeList					[7] RouteList 	OPTIONAL,
	travellingClassMark			[8] TravellingClassMark 	OPTIONAL,
	extensions				[9] Extensions  		OPTIONAL
	}
-- For the OPTIONAL parameters, refer to clause 2 for the trigger detection point processing rules 
-- to specify when these parameters are included in the message.

-- Direction: SSF ->  SCF, Timer: Ttd  
-- This operation is used for a disconnect indication (e.g. onhook, Q.931 Disconnect message, 
-- SS7 Release message) is received from the terminating party, or received from the originating party 
-- via the originating half BCSM. (DP  - T_Disconnect). 

TDisconnectArg  ::= SEQUENCE {
	dpSpecificCommonParameters		[0] DpSpecificCommonParameters ,
	calledPartyBusinessGroupID		[1] CalledPartyBusinessGroupID	OPTIONAL,
	calledPartySubaddress			[2] CalledPartySubaddress 	OPTIONAL,
	calledFacilityGroup				[3] FacilityGroup	OPTIONAL,
	calledFacilityGroupMember			[4] FacilityGroupMember	OPTIONAL,
	releaseCause					[5] Cause 	OPTIONAL,
	extensions					[6] Extensions  		OPTIONAL,
	connectTime					[7] Integer4	OPTIONAL,
	componentType				[8] ComponentType	OPTIONAL,
	component						[9] Component	OPTIONAL,
	componentCorrelationID			[10] ComponentCorrelationID	OPTIONAL
	}

-- Direction: SSF ->  SCF, Timer: Ttaa  
-- This operation is used for indication of incoming call received from originating half BCSM and authority 
-- to route call to a specified terminating resource (or group) verified. (DP  - Termination_Authorized). 

TermAttemptAuthorizedArg  ::= SEQUENCE {
	dpSpecificCommonParameters		[0] DpSpecificCommonParameters ,
	calledPartyBusinessGroupID		[1] CalledPartyBusinessGroupID	OPTIONAL,
	calledPartySubaddress			[2] CalledPartySubaddress 	OPTIONAL,
	callingPartyBusinessGroupID		[3] CallingPartyBusinessGroupID	OPTIONAL,
	originalCalledPartyID				[4] OriginalCalledPartyID 	OPTIONAL,
	redirectingPartyID				[5] RedirectingPartyID 	OPTIONAL,
	redirectionInformation				[6] RedirectionInformation	OPTIONAL,
	routeList						[7] RouteList 	OPTIONAL,
	travellingClassMark				[8] TravellingClassMark 	OPTIONAL,
	extensions					[9]  Extensions  		OPTIONAL,
	callingPartySubaddress			[10] CallingPartySubaddress 	OPTIONAL
	}
-- Direction: SSF -> SCF. Timer: Ttra
-- This operation is used for indication of a call termination attempt from the terminating half BCSM. (DP -
-- Termination_Attempt). 

TerminationAttemptArg  ::= SEQUENCE {
	dpSpecificCommonParameters 	[0] DpSpecificCommonParameters ,
	calledPartyBusinessGroupID	[1] CalledPartyBusinessGroupID	OPTIONAL,
	calledPartySubaddress		[2] CalledPartySubaddress 	OPTIONAL,
	callingPartyBusinessGroupID	[3] CallingPartyBusinessGroupID	OPTIONAL,
	callingPartySubaddress		[4] CallingPartySubaddress 	OPTIONAL,
	originalCalledPartyID			[5] OriginalCalledPartyID 	OPTIONAL,
	redirectingPartyID			[6] RedirectingPartyID 	OPTIONAL,
	redirectionInformation			[7] RedirectionInformation	OPTIONAL,
	routeList					[8] RouteList 	OPTIONAL,
	travellingClassMark			[9] TravellingClassMark 	OPTIONAL,
	extensions				[10] Extensions  		OPTIONAL
	}
-- For the OPTIONAL parameters, refer to clause 2 for the trigger detection point processing rules 
-- to specify when these parameters are included in the message.


-- Direction: SSF ->  SCF, Timer: Ttmc  
-- This operation is used to indicate that a feature request is received from the terminating party (e.g. hook 
-- flash, ISDN feature activation Q.931 HOLD or RETrieve message). (DP  - T_Mid_Call). 

-- Direction: SSF -> SCF, Timer: Ttna  
-- This operation is used to indicate that the terminating party does not answer within a specified duration. 
-- (DP  - T_No_Answer). . 

TNoAnswerArg  ::= SEQUENCE {
	dpSpecificCommonParameters		[0] DpSpecificCommonParameters ,
	calledPartyBusinessGroupID		[1] CalledPartyBusinessGroupID	OPTIONAL,
	calledPartySubaddress			[2] CalledPartySubaddress 	OPTIONAL,
	calledFacilityGroup				[3] FacilityGroup	OPTIONAL,
	calledFacilityGroupMember			[4] FacilityGroupMember	OPTIONAL,
	originalCalledPartyID				[5] OriginalCalledPartyID 	OPTIONAL,
	redirectingPartyID				[6] RedirectingPartyID 	OPTIONAL,
	redirectionInformation				[7] RedirectionInformation	OPTIONAL,
	travellingClassMark				[8] TravellingClassMark 	OPTIONAL,
	extensions					[9] Extensions  		OPTIONAL,
	componentType				[10] ComponentType	OPTIONAL,
	component						[11] Component	OPTIONAL,
	componentCorrelationID			[12] ComponentCorrelationID	OPTIONAL
	}

--	Direction: SSF -> SCF. Timer: T ts
--	This operation is issued by the SSF after detecting a valid trigger condition at the T_Suspend DP or  to 
--	report a tSuspended event requested by the RequestReportBCSMEvent. 

TSuspendedArg  ::= SEQUENCE {
	dpSpecificCommonParameters	 	[0] DpSpecificCommonParameters ,
	legID						[1] LegID		OPTIONAL,
	extensions					[2] Extensions  		OPTIONAL
	}
-- For the OPTIONAL parameters, refer to clause 2.1..27 for the trigger detection point processing rules 
-- to specify when these parameters are included in the message.
-- Use for T/EDP-R is ffs.




-- Direction: SCF -> SRF, Timer: Tpa
-- This operation is to be used after Establish Temporary Connection (assist procedure with a second SSP) 
-- or a Connect to Resource (no assist) operation. It may be used for inband interaction with an analog user, 
-- or for interaction with an ISDN user. In the former case, the SRF is usually collocated with the SSF for 
-- standard tones (congestion tone...) or standard announcements. In the latter case, the SRF is always 
-- collocated with the SSF in the switch. Any error is returned to the SCF. The timer associated with this 
-- operation must be of a sufficient duration to allow its linked operation to be correctly correlated.

PlayAnnouncementArg  ::= SEQUENCE {
	informationToSend	[0] InformationToSend ,
	disconnectFromIPForbidden	[1] BOOLEAN	DEFAULT TRUE,
	requestAnnouncementComplete	[2] BOOLEAN	DEFAULT TRUE,
	extensions	[3] Extensions 	OPTIONAL,
	connectedParty	CHOICE {
			legID	[4] LegID,
			callSegmentID	[5] CallSegmentID 
			} 	OPTIONAL
	}

-- Direction: SCF ->  SRF, Timer: Tpc 
-- This operation is used to interact with a user to collect information.

PromptAndCollectUserInformationArg  ::= SEQUENCE {
	collectedInfo	[0] CollectedInfo,
	disconnectFromIPForbidden	[1] BOOLEAN	DEFAULT TRUE,
	informationToSend 	[2] InformationToSend 	OPTIONAL,
	extensions	[3] Extensions  	OPTIONAL,
	callSegmentID	[4] CallSegmentID  	OPTIONAL
	}

ReceivedInformationArg  ::= CHOICE {
	digitsResponse	[0] Digits ,
	iA5Response	[1] IA5String,
	modemdetected 	[2] BOOLEAN
}

--  Direction: SCF ->SRF, Timer: Tprm
--  Used to prompt a user to store a message

PromptAndReceiveMessageArg  ::= SEQUENCE {
	disconnectFromIPForbidden	[0] BOOLEAN	DEFAULT TRUE,
	informationToSend	[1] InformationToSend 	OPTIONAL,
	extensions	[3] Extensions 	OPTIONAL,
	subscriberID	[4] GenericNumber 	OPTIONAL,
	mailBoxID	[5] MailBoxID 	OPTIONAL,
	informationToRecord	[6] InformationToRecord ,
	media	[7] Media ,	-- DEFAULT voiceMail,
	callSegmentID	[8] CallSegmentID 	OPTIONAL
	}

MessageReceivedArg 	::= SEQUENCE {
	receivedStatus	[0] ReceivedStatus,
	recordedMessageID	[1] RecordedMessageID	OPTIONAL,
	recordedMessageUnits	[2] INTEGER(1..maxRecordedMessageUnits)	OPTIONAL,
	extensions	[3] Extensions 	OPTIONAL
	}

-- reportUTSI OPERATION 
-- This operation is described in part 2 of the recommendation Q.1238. 


-- requestReportUTSI OPERATION 
-- This operation is described in part 2 of the recommendation Q.1238. 


-- sendSTUI OPERATION 
-- This operation is described in part 2 of the recommendation Q.1238. 


-- Direction:SCF-> SRF. Timer :TCl
-- This operation is issued by the SCF to deallocate the resources used to perform the
-- instance of the "User Interaction" script : the context is released.

ScriptCloseArg  ::= SEQUENCE {
	uIScriptId	Code,
	uIScriptSpecificInfo	[0] OCTET STRING	OPTIONAL,
	extensions	[1] Extensions 	OPTIONAL,
	callSegmentID	[2] CallSegmentID 	OPTIONAL
	}

-- Direction:SRF-> SCF. Timer :TRe
-- This operation is issued by the SRF to return information to the SCF on the results of the
-- execution of the instance of User Interaction script.

ScriptEventArg  ::= SEQUENCE {
	uIScriptId	Code,
	uIScriptResult	[0] OCTET STRING OPTIONAL,
	extensions	[1] Extensions 	OPTIONAL,
	callSegmentID	[2] CallSegmentID 	OPTIONAL,
	lastEventIndicator	[3] BOOLEAN 	DEFAULT  FALSE
	}

-- Direction:SCF-> SRF. Timer :Tinf

ScriptInformationArg ::= SEQUENCE {
	uIScriptId	Code,
	uIScriptSpecificInfo	[0] OCTET STRING	OPTIONAL,
	extensions	[1] Extensions 	OPTIONAL,
	callSegmentID	[2] CallSegmentID	OPTIONAL
	}

-- Direction:SCF-> SRF. Timer :Tru
-- This operation is issued by the SCF to allocate the necessary resources to perform the
-- instance of the "User Interaction" script and then to activate this "User Interaction" script
-- instance. A context is partially defined for it if necessary.

ScriptRunArg  ::= SEQUENCE {
	uIScriptId	Code,
	uIScriptSpecificInfo	[0] OCTET STRING OPTIONAL,
	extensions	[1] Extensions 	OPTIONAL,
	disconnectFromIPForbidden	[2] BOOLEAN	DEFAULT TRUE,
	callSegmentID	[3] CallSegmentID 	OPTIONAL
	}

-- Direction: SRF ->  SCF, Timer: Tsrr  
-- This operation is used as  the response to a PlayAnnouncement operation when the announcement completed 
-- report indication is set.  

SpecializedResourceReportArg ::=   NULL

-- Direction: SRF ->  SCF, Timer: Tcg   
-- This operation is used to request the SCF  to reduce the rate at which specific service requests are sent to 
-- the  SRF.  

SRFCallGapArg  ::= SEQUENCE {
	sRFgapCriteria	[0] SRFGapCriteria ,
	gapIndicators	[1] GapIndicators,
	controlType	[2] ControlType	OPTIONAL,
	extensions	[3] Extensions  	OPTIONAL
	}





END
