INCS3BundleArg
DEFINITIONS IMPLICIT TAGS ::= 
BEGIN
IMPORTS
					-- 29.09.1998 changed to contain SRF
					-- arguments. For that purpose INCS2SSFSCFopsargs
					-- and INCS2SCFSRFopsargs have been merged to
					-- INCS2opsargs
	CancelFailed,
	RequestedInfoError,
	SystemFailure,
	TaskRefused,
	ActivateServiceFilteringArg, 
	AnalysedInformationArg,
	AnalyseInformationArg,
	ApplyChargingArg ,
	ApplyChargingReportArg ,
	AssistRequestInstructionsArg ,
	AuthorizeTerminationArg,
	CallGapArg ,
	CallInformationReportArg ,
	CallInformationRequestArg , 
	CancelArg ,
	CancelStatusReportRequestArg,
	CollectedInformationArg,
	CollectInformationArg ,
	ConnectArg ,
	ConnectToResourceArg,
	ContinueWithArgumentArg ,
	CreateCallSegmentAssociationArg ,
	CreateCallSegmentAssociationResultArg ,
	CreateOrRemoveTriggerDataArg,
	CreateOrRemoveTriggerDataResultArg,
	DisconnectForwardConnectionWithArgumentArg ,
	DisconnectLegArg ,
	EntityReleasedArg , 
	EstablishTemporaryConnectionArg ,
	EventNotificationChargingArg ,
	EventReportBCSMArg ,
	EventReportFacilityArg,
	FacilitySelectedAndAvailableArg,
	FurnishChargingInformationArg ,
	HoldCallInNetworkArg,
	InitialDPArg ,
	InitiateCallAttemptArg ,
	ManageTriggerDataArg , 
	ManageTriggerDataResultArg  ,
	MergeCallSegmentsArg ,
	MoveCallSegmentsArg ,
	MoveLegArg ,
	OAbandonArg,
	OAnswerArg,
	OCalledPartyBusyArg,
	ODisconnectArg,
	MidCallArg,
	ONoAnswerArg,
	OriginationAttemptArg,
	OriginationAttemptAuthorizedArg,
	OSuspendedArg,
	ReconnectArg,
	ReleaseCallArg ,
	ReportUTSIArg ,
	RequestCurrentStatusReportArg,
	RequestEveryStatusChangeReportArg,
	RequestFirstStatusMatchReportArg,
	RequestNotificationChargingEventArg,
	RequestReportBCSMEventArg , 
	RequestReportFacilityEventArg,
	RequestReportUTSIArg ,
	ResetTimerArg ,
	RouteSelectFailureArg,
	SelectFacilityArg,
	SelectRouteArg,
	SendChargingInformationArg ,
	SendFacilityInformationArg,
	SendSTUIArg ,
	ServiceFilteringResponseArg ,
	SetServiceProfileArg,
	SplitLegArg ,
	StatusReportArg,
	TAnswerArg,
	TBusyArg,
	TDisconnectArg,
	TermAttemptAuthorizedArg,
	TerminationAttemptArg,
	TNoAnswerArg,
	TSuspendedArg,

	-- from now on SRF arguments
	MessageReceivedArg ,
	PlayAnnouncementArg ,
	PromptAndCollectUserInformationArg ,
	PromptAndReceiveMessageArg ,
	ReceivedInformationArg ,
	ScriptCloseArg ,
	ScriptEventArg ,
	ScriptInformationArg ,
	ScriptRunArg ,
	SpecializedResourceReportArg
	

FROM INCS3opsargs 

;

Empty	::= NULL

ArgType ::= CHOICE	
	{	aSFArg 		 [0] ActivateServiceFilteringArg,
		aSFRArg		 [1] Empty,
                aTArg            [2] Empty,
                aTRArg         	 [3] Empty,
		aCArg		 [4] ApplyChargingArg ,
		aCRArg		 [5] ApplyChargingReportArg ,
		aRIArg		 [6] AssistRequestInstructionsArg ,
		cGArg		 [7] CallGapArg ,
		cIRArg		 [8] CallInformationReportArg ,
		cIRQArg		 [9] CallInformationRequestArg , 
		cANArg		[10] CancelArg ,
		cIArg		[11] CollectInformationArg ,
		cONArg		[12] ConnectArg ,
		cTRArg		[13] ConnectToResourceArg,
		cWAArg		[14] ContinueWithArgumentArg ,
		cSAArg		[15] CreateCallSegmentAssociationArg ,
		cSARArg		[16] CreateCallSegmentAssociationResultArg ,
		cUEArg          [17] Empty,
		dFCArg		[99] Empty,
		dFCWAArg	[18] DisconnectForwardConnectionWithArgumentArg ,
		dLArg		[19] DisconnectLegArg ,
		dLRArg		[20] Empty,
		eRArg		[21] EntityReleasedArg , 
		eTCArg		[22] EstablishTemporaryConnectionArg ,
		eNCArg		[23] EventNotificationChargingArg ,
		eRBArg		[24] EventReportBCSMArg ,
		fCIArg		[25] FurnishChargingInformationArg ,
		iDPArg		[26] InitialDPArg ,
		iCAArg		[27] InitiateCallAttemptArg ,
		mTDArg		[28] ManageTriggerDataArg , 
		mTDRArg		[29] ManageTriggerDataResultArg,
		mCArg		[30] MergeCallSegmentsArg,
		mCRArg		[31] Empty,
		mCSArg		[32] MoveCallSegmentsArg,
		mCSRArg		[33] Empty,
		mLArg		[34] MoveLegArg,
		mLRArg		[35] Empty,
		rCArg		[36] ReleaseCallArg ,
		rUArg		[37] ReportUTSIArg ,
		rNCArg		[38] RequestNotificationChargingEventArg , 
		rRBArg		[39] RequestReportBCSMEventArg , 
		rRUArg		[40] RequestReportUTSIArg ,
		rTArg		[41] ResetTimerArg ,
		sCIArg		[42] SendChargingInformationArg ,
		sSArg		[43] SendSTUIArg ,
		sFRArg		[44] ServiceFilteringResponseArg ,
		sLArg		[45] SplitLegArg ,
		sLRArg		[46] Empty ,
 		-- SRF
		pAArg		[47] PlayAnnouncementArg ,
		mRArg		[48] MessageReceivedArg ,
		pACArg		[49] PromptAndCollectUserInformationArg ,
		pARArg		[50] PromptAndReceiveMessageArg ,
		rIArg		[51] ReceivedInformationArg ,
		sCArg		[52] ScriptCloseArg ,
		sEArg		[53] ScriptEventArg ,
		sIArg		[54] ScriptInformationArg ,
		sCRArg		[55] ScriptRunArg ,
		sRRArg		[56] SpecializedResourceReportArg,
		-- ITU CS-3
		aDIArg		[98] AnalysedInformationArg,
		aIArg		[97] AnalyseInformationArg,
		aUTTArg		[96] AuthorizeTerminationArg,
		cDI		[95] CollectedInformationArg,
		cTDArg		[94] CreateOrRemoveTriggerDataArg,
		cTDRArg		[93] CreateOrRemoveTriggerDataResultArg,
		eRFArg		[92] EventReportFacilityArg,
		fSAArg		[91] FacilitySelectedAndAvailableArg,
		oABNArg		[90] OAbandonArg,
		oANSArg		[89] OAnswerArg,
		oCPBArg		[88] OCalledPartyBusyArg,
		oDISArg		[87] ODisconnectArg,
		mIDCLArg	[86] MidCallArg,
		oNOANSArg	[85] ONoAnswerArg,
		oAArg		[84] OriginationAttemptArg,
		oAAArg		[83] OriginationAttemptAuthorizedArg,
		oSUSArg		[82] OSuspendedArg,
		rECONArg	[81] ReconnectArg,
		rCSRArg		[80] RequestCurrentStatusReportArg,
		rESCRArg	[79] RequestEveryStatusChangeReportArg,
		rFSMRArg	[78] RequestFirstStatusMatchReportArg,
		rRFEArg		[77] RequestReportFacilityEventArg,
		rSFArg		[76] RouteSelectFailureArg,
		sFArg		[75] SelectFacilityArg,
		sRArg	[74] SelectRouteArg,
		sENDFArg		[73] SendFacilityInformationArg,
		sSPArg		[72] SetServiceProfileArg,
		sREPArg		[71] StatusReportArg,
		tANSArg		[70] TAnswerArg,
		tBUSArg		[69] TBusyArg,
		tDISArg		[68] TDisconnectArg,
		tAAArg		[67] TermAttemptAuthorizedArg,
		tAArg		[66] TerminationAttemptArg,
		tNOANSArg	[65] TNoAnswerArg,
		tSUSArg		[64] TSuspendedArg,
		hCINArg	[63] HoldCallInNetworkArg
	}

ErrorType ::= CHOICE	
	{	cancelPar			 [0] Empty,
		cancelFailedPar			 [1] CancelFailed,
		chainingRefusedPar		 [2] Empty,
		eTCFailedPar			 [3] Empty,
		improperCallerResponsePar	 [4] Empty,
		missingCustomerRecordPar	 [5] Empty,
		missingParameterPar		 [6] Empty,
		parameterOutOfRangePar		 [7] Empty,
		requestedInfoError		 [8] RequestedInfoError,
		systemFailurePar		 [9] SystemFailure,
		taskRefusedPar			[10] TaskRefused,	
		unavailableResourcePar		[11] Empty,
		unexpectedComponentSequencePar	[12] Empty,
		unexpectedDataValuePar		[13] Empty,
		unexpectedParameterPar		[14] Empty,
		unknownLegIDPar			[15] Empty,
		unknownRecordedMessageID	[16] Empty,
		unknownResource			[17] Empty,
		unknownSubscriber		[18] Empty	
	}
END
